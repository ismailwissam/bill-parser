SIEMENS-CDR DEFINITIONS IMPLICIT TAGS  ::=

BEGIN

--
-- Structure of a Siemens CDR
--

DataChange ::= CHOICE 
{
	sr9Siemens	Sr9Siemens, 
...
}


--
--Siemens SR9 CDR
--

Sr9Siemens ::= [PRIVATE 1] SET
{
	traceType			TraceType			OPTIONAL,
	traceReference			TraceReference			OPTIONAL,
	recordType			RecordType			OPTIONAL,
	callTransactionType		CallTransactionType		OPTIONAL,
	servedOtherNumber		ServedOtherNumber		OPTIONAL,
	servedMobileNumber		ServedMobileNumber		OPTIONAL,
	chargingtimeData		ChargingtimeData		OPTIONAL,
	timeQuality			TimeQuality			OPTIONAL,
	transactionIdentification	TransactionIdentification	OPTIONAL,
	otherPartyShortNumber		OtherPartyShortNumber		OPTIONAL,
	otherPartySMS			OtherPartySMS			OPTIONAL,
	otherPartySequence		OtherPartySequence		OPTIONAL,
	otherMSRN			OtherMSRN			OPTIONAL,
	origTermMscId			OrigTermMscId			OPTIONAL,
	origTermBscId			OrigTermBscId			OPTIONAL,
	individualTeleserviceNumber	IndividualTeleserviceNumber	OPTIONAL,
	individualBearerserviceNumber	IndividualBearerserviceNumber	OPTIONAL,
	iSDNBasicService		ISDNBasicService		OPTIONAL,
	transmissionMode		TransmissionMode		OPTIONAL,
	outgTgTCompBlock		OutgTgTCompBlock		OPTIONAL,
	causeForTermination		CauseForTermination		OPTIONAL,
	reasonForTermination		ReasonForTermination		OPTIONAL,
	msClassmark			MsClassmark			OPTIONAL,
	locationNumber			LocationNumber			OPTIONAL,
	cellId				CellId				OPTIONAL,
	exchangeId			ExchangeId			OPTIONAL,
	incTgTCompBlock			IncTgTCompBlock			OPTIONAL,
	sequenceNumber			SequenceNumber			OPTIONAL,
	intermediateSequenceNumber	OCTET STRING			OPTIONAL,
	supplServiceInfo		SupplServiceInfo		OPTIONAL,
	msAccessRate			MsAccessRate			OPTIONAL,
	chargeAdviceInformation		ChargeAdviceInformation		OPTIONAL,
	thirdParty			ThirdParty			OPTIONAL,
	serviceCentreAddress		ServiceCentreAddress		OPTIONAL,
	sMTransmissionResult		SMTransmissionResult		OPTIONAL,
	hotTransferResult		HotTransferResult		OPTIONAL,
	chargeIndicator			ChargeIndicator			OPTIONAL,
	chargingPulses			ChargingPulses			OPTIONAL,
	redirectionCounter		RedirectionCounter		OPTIONAL,
	multipleSMTransfer		MultipleSMTransfer		OPTIONAL,
	drcCallId			DrcCallId			OPTIONAL,
	drcCallRN			DrcCallRN			OPTIONAL,
	drcChrgOrigin			DrcChrgOrigin			OPTIONAL,
	drcTariffClass			DrcTariffClass			OPTIONAL,
	secondCellId			SecondCellId			OPTIONAL,
	usedEmlppPriority		UsedEmlppPriority		OPTIONAL,
	partialRecordType		PartialRecordType		OPTIONAL,
	protocolIdForSMS		ProtocolIdForSMS		OPTIONAL,
...
}


--
--Type Define
--

TraceType ::= [PRIVATE 53] OCTET STRING

TraceReference ::= [PRIVATE 52] OCTET STRING

RecordType ::= [PRIVATE 2]  INTEGER

CallTransactionType ::= [PRIVATE 3]  INTEGER

ServedOtherNumber ::= [PRIVATE 40] OCTET STRING

ServedMobileNumber ::= [PRIVATE 39] SEQUENCE
{
	servedIMSI	ServedIMSI	OPTIONAL,
	servedMSIsdn	ServedMSIsdn	OPTIONAL,
	servedIMEI	ServedIMEI	OPTIONAL,
	servedMSRN	ServedMSRN	OPTIONAL,
	pABXNumber	PABXNumber	OPTIONAL,
...
}
ServedIMSI   ::= [PRIVATE 6]  OCTET STRING
ServedMSIsdn ::= [PRIVATE 7]  OCTET STRING
ServedIMEI   ::= [PRIVATE 8]  OCTET STRING
ServedMSRN   ::= [PRIVATE 29] OCTET STRING
PABXNumber   ::= [PRIVATE 72] OCTET STRING


ChargingtimeData ::= [PRIVATE 13] SEQUENCE  --Constructed PRIVATE 13
{
	startOfChargingdate	StartOfChargingdate	OPTIONAL,
	startOfChargingtime	StartOfChargingtime	OPTIONAL,
	callDuration		CallDuration		OPTIONAL,
...
}
StartOfChargingdate ::= [PRIVATE 19] OCTET STRING
StartOfChargingtime ::= [PRIVATE 20] SET
{
	timeStamp	TimeStamp	OPTIONAL,
...
}
TimeStamp    ::= [PRIVATE 28] OCTET STRING
CallDuration ::= [PRIVATE 17] INTEGER

TimeQuality ::= [PRIVATE 4] OCTET STRING

TransactionIdentification ::= [PRIVATE 5] OCTET STRING

OtherPartyShortNumber ::= [PRIVATE 45] OCTET STRING

OtherPartySMS ::= [APPLICATION 13] OCTET STRING    --Redefine Primitive PRIVATE 13

OtherPartySequence ::= [PRIVATE 93] SEQUENCE
{
	dialledOtherParty	DialledOtherParty	OPTIONAL,
	translatedOtherParty	TranslatedOtherParty	OPTIONAL,
...
}
DialledOtherParty    ::= [PRIVATE 94] OCTET STRING
TranslatedOtherParty ::= [PRIVATE 95] OCTET STRING

OtherMSRN ::= [PRIVATE 60] OCTET STRING

OrigTermMscId ::= [PRIVATE 10] OCTET STRING

OrigTermBscId ::= [PRIVATE 11] OCTET STRING

IndividualTeleserviceNumber ::= [PRIVATE 12] OCTET STRING

IndividualBearerserviceNumber ::= [PRIVATE 14] OCTET STRING

ISDNBasicService ::= [PRIVATE 73] OCTET STRING

TransmissionMode ::= [PRIVATE 15] OCTET STRING

OutgTgTCompBlock ::= [PRIVATE 27] SEQUENCE
{
	tgrpNameOg	IA5String	OPTIONAL,
	cicOg		CicOg		OPTIONAL,
...
}
CicOg ::= [PRIVATE 16] OCTET STRING

CauseForTermination ::= [PRIVATE 18] OCTET STRING

ReasonForTermination ::= [PRIVATE 81] OCTET STRING

MsClassmark ::= [PRIVATE 21] OCTET STRING

LocationNumber ::= [PRIVATE 35] OCTET STRING

CellId ::= [PRIVATE 22] OCTET STRING

ExchangeId ::= [PRIVATE 30] IA5String

IncTgTCompBlock ::= [PRIVATE 33] SEQUENCE
{
	tgrpNameIc	IA5String	OPTIONAL,
	cicIc		CicOg           OPTIONAL,
...
}

SequenceNumber ::= [PRIVATE 48] OCTET STRING

SupplServiceInfo ::= [PRIVATE 23] SEQUENCE
{
	callHoldInvocCount	CallHoldInvocCount	OPTIONAL,
	callWaitInvocCount	CallWaitInvocCount	OPTIONAL,
	sSSequenceOf		SSSequenceOf		OPTIONAL,
...
}
CallHoldInvocCount ::= [PRIVATE 41] INTEGER
CallWaitInvocCount ::= [PRIVATE 42] INTEGER
SSSequenceOf ::= [PRIVATE 43] SEQUENCE
{
	sSCode	SSCode	OPTIONAL,
...
}
SSCode ::= [PRIVATE 9] OCTET STRING

MsAccessRate ::= [PRIVATE 24] INTEGER

ChargeAdviceInformation ::= [PRIVATE 43] SEQUENCE
{
	chargeAdviceElement	ChargeAdviceElement	OPTIONAL,
...
}
ChargeAdviceElement ::= [PRIVATE 26] OCTET STRING

ThirdParty ::= [PRIVATE 32] OCTET STRING

ServiceCentreAddress ::= [PRIVATE 38] OCTET STRING

SMTransmissionResult ::= [PRIVATE 50] OCTET STRING

HotTransferResult ::= [PRIVATE 46] OCTET STRING

ChargeIndicator ::= [PRIVATE 47] INTEGER

ChargingPulses ::= [PRIVATE 51] INTEGER

RedirectionCounter ::= [PRIVATE 70] INTEGER

MultipleSMTransfer ::= [PRIVATE 71] OCTET STRING

DrcCallId ::= [PRIVATE 25] OCTET STRING

DrcCallRN ::= [PRIVATE 31] OCTET STRING

DrcChrgOrigin ::= [PRIVATE 36] OCTET STRING

DrcTariffClass ::= [PRIVATE 37] OCTET STRING

SecondCellId ::= [PRIVATE 82] OCTET STRING

UsedEmlppPriority ::= [PRIVATE 92] OCTET STRING

PartialRecordType ::= [PRIVATE 96]  ENUMERATED
{
	timeLimit(0),
	serviceChange(1),
	locationChange(2),
	classmarkChange(3),
	aocParmChange(4),
	radioChannelChange(5),
	hSCSDParmChange(6),
	changeOfCAMELDestination(7),
	callTransferInvocation(8),
	changeOfChargeParam(9),
	changeOfDestination(14)
}

ProtocolIdForSMS ::= [PRIVATE 97] OCTET STRING


END
